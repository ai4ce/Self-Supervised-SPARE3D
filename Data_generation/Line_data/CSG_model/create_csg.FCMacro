import os
import ImportGui
import glob
import FreeCAD, Part, Drawing, Draft, DrawingGui, TechDraw
import TechDrawGui
import random


#add a cube
def AddCube(Boxname):
    App.ActiveDocument.addObject("Part::Box",Boxname)
    App.ActiveDocument.ActiveObject.Label = Boxname
    App.ActiveDocument.recompute()
    Gui.SendMsgToActiveView("ViewFit")

    #randomly set placement the index
    AngleI = random.randint(0,4)
    Angle = AngleI * 90
    index = random.randint(1,3)
    if index == 1:
        AppRX = random.randint(-1,1)
        AppRY = 0
        AppRZ = 0
    if index == 2:
        AppRY = random.randint(-1,1)
        AppRX = 0
        AppRZ = 0
    if index == 3:
        AppRZ = random.randint(-1,1)
        AppRY = 0
        AppRX = 0
    X = random.randint(0,10)
    Y = random.randint(0,10)
    Z = random.randint(0,10)
    FreeCAD.getDocument("Unnamed").getObject(Boxname).Placement = App.Placement(App.Vector(X,Y,Z),App.Rotation(App.Vector(AppRX,AppRY,AppRZ),Angle))
    
    #set model index
    L = random.randint(5,50)
    W = random.randint(5,50)
    H = random.randint(5,50)
    FreeCAD.getDocument("Unnamed").getObject(Boxname).Length = str(L) + "mm"
    FreeCAD.getDocument("Unnamed").getObject(Boxname).Width = str(W) + "mm"
    FreeCAD.getDocument("Unnamed").getObject(Boxname).Height = str(H) + "mm"


def AddCylinder(Cylindername):
    App.ActiveDocument.addObject("Part::Cylinder",Cylindername)
    App.ActiveDocument.ActiveObject.Label = Cylindername
    App.ActiveDocument.recompute()
    Gui.SendMsgToActiveView("ViewFit")

    #randomly set placement the index
    AngleI = random.randint(0,4)
    Angle = AngleI * 90
    index = random.randint(1,3)
    if index == 1:
        AppRX = random.randint(-1,1)
        AppRY = 0
        AppRZ = 0
    if index == 2:
        AppRY = random.randint(-1,1)
        AppRX = 0
        AppRZ = 0
    if index == 3:
        AppRZ = random.randint(-1,1)
        AppRY = 0
        AppRX = 0
    X = random.randint(0,10)
    Y = random.randint(0,10)
    Z = random.randint(0,10)
    FreeCAD.getDocument("Unnamed").getObject(Cylindername).Placement = App.Placement(App.Vector(X,Y,Z),App.Rotation(App.Vector(AppRX,AppRY,AppRZ),Angle))

    #set model index
    R = random.randint(1,25)
    H = random.randint(1,50)
    Ang = random.randint(1,360)
    FreeCAD.getDocument("Unnamed").getObject(Cylindername).Radius = str(R) + "mm"
    FreeCAD.getDocument("Unnamed").getObject(Cylindername).Height = str(H) + "mm"
    FreeCAD.getDocument("Unnamed").getObject(Cylindername).Angle = str(Ang) + " deg"

def AddShere(Sherename):
    App.ActiveDocument.addObject("Part::Sphere",Sherename)
    App.ActiveDocument.ActiveObject.Label = Sherename
    App.ActiveDocument.recompute()
    Gui.SendMsgToActiveView("ViewFit")

    #randomly set placement the index
    AngleI = random.randint(0,4)
    Angle = AngleI * 90
    index = random.randint(1,3)
    if index == 1:
        AppRX = random.randint(-1,1)
        AppRY = 0
        AppRZ = 0
    if index == 2:
        AppRY = random.randint(-1,1)
        AppRX = 0
        AppRZ = 0
    if index == 3:
        AppRZ = random.randint(-1,1)
        AppRY = 0
        AppRX = 0
    X = random.randint(0,10)
    Y = random.randint(0,10)
    Z = random.randint(0,10)
    FreeCAD.getDocument("Unnamed").getObject(Sherename).Placement = App.Placement(App.Vector(X,Y,Z),App.Rotation(App.Vector(AppRX,AppRY,AppRZ),Angle))

    #randomly set the index of the Sphere
    R = random.randint(5,25)
    Ang1 = random.randint(1,360)
    Ang2 = random.randint(1,360)
    Ang3 = random.randint(1,360)

    FreeCAD.getDocument("Unnamed").getObject(Sherename).Radius = str(R) + "mm"
    FreeCAD.getDocument("Unnamed").getObject(Sherename).Angle1 = str(Ang1) + " deg"
    FreeCAD.getDocument("Unnamed").getObject(Sherename).Angle1 = str(Ang2) + " deg"
    FreeCAD.getDocument("Unnamed").getObject(Sherename).Angle1 = str(Ang3) + " deg"


def AddCone(Conename):
    App.ActiveDocument.addObject("Part::Cone",Conename)
    App.ActiveDocument.ActiveObject.Label = Conename
    App.ActiveDocument.recompute()
    Gui.SendMsgToActiveView("ViewFit")

    #randomly set placement the index
    AngleI = random.randint(0,4)
    Angle = AngleI * 90
    index = random.randint(1,3)
    if index == 1:
        AppRX = random.randint(-1,1)
        AppRY = 0
        AppRZ = 0
    if index == 2:
        AppRY = random.randint(-1,1)
        AppRX = 0
        AppRZ = 0
    if index == 3:
        AppRZ = random.randint(-1,1)
        AppRY = 0
        AppRX = 0
    X = random.randint(0,10)
    Y = random.randint(0,10)
    Z = random.randint(0,10)
    FreeCAD.getDocument("Unnamed").getObject(Conename).Placement = App.Placement(App.Vector(X,Y,Z),App.Rotation(App.Vector(AppRX,AppRY,AppRZ),Angle))

    R1 = random.randint(5,25)
    R2 = random.randint(10,50)
    H = random.randint(1,50)
    Ang = random.randint(1,360)
    FreeCAD.getDocument("Unnamed").getObject(Conename).Radius1 = str(R1) + "mm"
    FreeCAD.getDocument("Unnamed").getObject(Conename).Radius2 = str(R2) + "mm"
    FreeCAD.getDocument("Unnamed").getObject(Conename).Height = str(H) + "mm"
    FreeCAD.getDocument("Unnamed").getObject(Conename).Angle = str(Ang) + " deg"


def AddTorus(TorusName):
    App.ActiveDocument.addObject("Part::Torus",TorusName)
    App.ActiveDocument.ActiveObject.Label = TorusName
    App.ActiveDocument.recompute()
    Gui.SendMsgToActiveView("ViewFit")

     #randomly set placement the index
    AngleI = random.randint(0,4)
    Angle = AngleI * 90
    index = random.randint(1,3)
    if index == 1:
        AppRX = random.randint(-1,1)
        AppRY = 0
        AppRZ = 0
    if index == 2:
        AppRY = random.randint(-1,1)
        AppRX = 0
        AppRZ = 0
    if index == 3:
        AppRZ = random.randint(-1,1)
        AppRY = 0
        AppRX = 0
    X = random.randint(0,10)
    Y = random.randint(0,10)
    Z = random.randint(0,10)
    FreeCAD.getDocument("Unnamed").getObject(TorusName).Placement = App.Placement(App.Vector(X,Y,Z),App.Rotation(App.Vector(AppRX,AppRY,AppRZ),Angle))

    R1 = random.randint(5,25)
    R2 = random.randint(10,50)
    Ang1 = random.randint(-180,180)
    Ang2 = random.randint(-180,180)
    Ang3 = random.randint(1,360)

    FreeCAD.getDocument("Unnamed").getObject(TorusName).Radius1 = str(R1) + " mm"
    FreeCAD.getDocument("Unnamed").getObject(TorusName).Radius2 = str(R2) + " mm"
    FreeCAD.getDocument("Unnamed").getObject(TorusName).Angle1 = str(Ang1) + " deg"
    FreeCAD.getDocument("Unnamed").getObject(TorusName).Angle2 = str(Ang2) + " deg"
    FreeCAD.getDocument("Unnamed").getObject(TorusName).Angle3 = str(Ang3) + " deg"


def CutAction():
    Gui.Selection.clearSelection()
    ob=[]
    for obj in FreeCAD.ActiveDocument.Objects:
        if obj.ViewObject.isVisible():
            Gui.Selection.addSelection(obj)
            ob.append(obj)
    S1  = random.randint(0,(len(ob)-1))
#    S2  = random.choice([i for i in range(len(ob)) if i not S1])
        
    App.activeDocument().addObject("Part::Cut","Cut")
    App.activeDocument().Cut.Base = ob[0]
    App.activeDocument().Cut.Tool = ob[S1]

    App.getDocument("Unnamed").recompute()


def Randomproduce():
    Index = random.randint(1,4)
    if Index == 1:
        AddCube("Box")
    if Index == 2:
        AddCylinder("Cylinder")
    if Index == 3:
        AddCone("cone")
    if Index == 4:
        AddShere("Shere")
	# if Index == 5:
        # AddTorus("Torus")
	
	
def ProduceAndExport(num,name):
    for i in range(num):
        Randomproduce()
    CutAction()
    Gui.SendMsgToActiveView("ViewFit")
    ob=[]
    for obj in FreeCAD.ActiveDocument.Objects:
        if obj.ViewObject.isVisible():
            Gui.Selection.addSelection(obj)
            ob.append(obj)
    filename = "/data_1/SPARE3D/Code/CSG_script/test/"+str(num)+"_shape/"+ str(name)+".step"
    ImportGui.export(ob,filename)
    del ob
    App.ActiveDocument.recompute()


for n in range(0,7000):
    FreeCAD.newDocument()
    FreeCADGui.activeDocument().activeView().viewDefaultOrientation()

    from StartPage import StartPage
    StartPage.postStart()

    App.setActiveDocument("Unnamed")
    App.ActiveDocument=App.getDocument("Unnamed")
    Gui.ActiveDocument=Gui.getDocument("Unnamed")
    Gui.activateWorkbench("PartWorkbench")

    ProduceAndExport(28,n)
    App.closeDocument("Unnamed")
